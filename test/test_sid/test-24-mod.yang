module test-24-mod {
    yang-version 1.1;
    namespace "test-24-mod:uri";
    prefix t24;

    include test-24-sub;

    container top {
        list item {
            key name;
            leaf name {
                type string;
            }
        }
    }
}
